(vl-load-com)

;; ============================================================
;; MATCH DRAWING NAMES + CREATE DSD SHEET LISTS
;; Command: MATCHDRAWING
;; ============================================================

(defun MDN-GetAllDwgs (folder / result item fullpath)
  (setq result '())
  (foreach item (vl-directory-files folder "*.dwg" 1)
    (setq result (cons (strcat folder "\\" item) result))
  )
  (foreach item (vl-directory-files folder nil -1)
    (if (and (/= item ".") (/= item ".."))
      (progn
        (setq fullpath (strcat folder "\\" item))
        (setq result (append result (MDN-GetAllDwgs fullpath)))
      )
    )
  )
  result
)

(defun MDN-GetAllFolders (folder / result item fullpath)
  (setq result (list folder))
  (foreach item (vl-directory-files folder nil -1)
    (if (and (/= item ".") (/= item ".."))
      (progn
        (setq fullpath (strcat folder "\\" item))
        (setq result (append result (MDN-GetAllFolders fullpath)))
      )
    )
  )
  result
)

(defun MDN-GetFolderDwgs (folder / result item)
  (setq result '())
  (foreach item (vl-directory-files folder "*.dwg" 1)
    (setq result (cons item result))
  )
  (reverse result)
)

(defun MDN-GetAttributeValue (doc targetTag / layout block ent attributes att tag value found)
  (setq found nil)
  (vlax-for layout (vla-get-Layouts doc)
    (if (null found)
      (progn
        (setq block (vla-get-Block layout))
        (vlax-for ent block
          (if (and (null found)
                   (= (vla-get-ObjectName ent) "AcDbBlockReference")
                   (= (vla-get-HasAttributes ent) :vlax-true))
            (progn
              (setq attributes (vlax-invoke ent 'GetAttributes))
              (foreach att attributes
                (if (null found)
                  (progn
                    (setq tag (strcase (vla-get-TagString att)))
                    (if (= tag (strcase targetTag))
                      (progn
                        (setq value (vl-string-trim " " (vla-get-TextString att)))
                        (if (/= value "") (setq found value))
                      )
                    )
                  )
                )
              )
            )
          )
        )
      )
    )
  )
  found
)

(defun MDN-CleanName (name / upper len)
  (if name
    (progn
      (setq name (vl-string-trim " " name))
      (setq upper (strcase name))
      (setq len (strlen name))
      (if (and (> len 4) (= (substr upper (- len 3) 4) ".DWG"))
        (setq name (substr name 1 (- len 4)))
      )
    )
  )
  name
)

(defun MDN-LastDash (text / i pos)
  (setq i 1 pos nil)
  (while (<= i (strlen text))
    (if (= (substr text i 1) "-") (setq pos i))
    (setq i (1+ i))
  )
  pos
)

(defun MDN-RemoveLastToken (text / pos)
  (setq pos (MDN-LastDash text))
  (if pos (substr text 1 (1- pos)) text)
)

(defun MDN-GetSheetType (filename / base noSheet pos)
  (setq base (strcase (vl-filename-base filename)))
  (setq noSheet (MDN-RemoveLastToken base))
  (setq pos (MDN-LastDash noSheet))
  (if pos (substr noSheet (1+ pos)) "")
)

(defun MDN-GetSheetNumber (filename / base pos)
  (setq base (strcase (vl-filename-base filename)))
  (setq pos (MDN-LastDash base))
  (if pos (substr base (1+ pos)) "")
)

(defun MDN-TypeOrder (filename / typ)
  (setq typ (MDN-GetSheetType filename))
  (cond
    ((= typ "C") 1)
    ((= typ "M") 2)
    ((= typ "E") 3)
    ((= typ "IO") 4)
    ((= typ "I") 5)
    (T 99)
  )
)

(defun MDN-SortKey (filename / ord num)
  (setq ord (MDN-TypeOrder filename))
  (setq num (MDN-GetSheetNumber filename))
  (strcat (if (< ord 10) "0" "") (itoa ord) "-" num "-" (strcase filename))
)

(defun MDN-SortDwgs (dwgs)
  (vl-sort dwgs '(lambda (a b) (< (MDN-SortKey a) (MDN-SortKey b))))
)

(defun MDN-DrawingSetBase (filename / base)
  (setq base (vl-filename-base filename))
  (MDN-RemoveLastToken (MDN-RemoveLastToken base))
)

(defun MDN-GetDsdBaseName (folder dwgs prefix / folderName drawingBase upperFolder upperBase)
  (setq folderName (vl-filename-base folder))
  (setq drawingBase (MDN-DrawingSetBase (car dwgs)))
  (setq upperFolder (strcase folderName))
  (setq upperBase (strcase drawingBase))
  ;; ER folders such as ER18 that directly contain a panel's drawings.
  (if (and (wcmatch upperFolder "ER##")
           (wcmatch upperBase (strcat upperFolder "-BMS-PNL-##")))
    (if (/= prefix "") (strcat prefix "-" drawingBase) drawingBase)
    folderName
  )
)

(defun MDN-WriteDsdSheet (f drawing / base)
  (setq base (vl-filename-base drawing))
  (write-line (strcat "[DWF6Sheet:" base "-Layout1]") f)
  (write-line (strcat "DWG=./" drawing) f)
  (write-line "Layout=Layout1" f)
  (write-line "Setup=" f)
  (write-line (strcat "OriginalSheetPath=./" drawing) f)
  (write-line "Has Plot Port=0" f)
  (write-line "Has3DDWF=0" f)
)

(defun MDN-WriteDsd (folder dwgs dsdBase / dsdPath f drawing)
  (setq dsdPath (strcat folder "\\" dsdBase ".dsd"))
  (if (findfile dsdPath) (vl-file-delete dsdPath))
  (setq f (open dsdPath "w"))
  (if f
    (progn
      (write-line "[DWF6Version]" f)
      (write-line "Ver=1" f)
      (write-line "[DWF6MinorVersion]" f)
      (write-line "MinorVer=1" f)
      (foreach drawing dwgs (MDN-WriteDsdSheet f drawing))
      (write-line "[Target]" f)
      (write-line "Type=6" f)
      (write-line "DWF=" f)
      (write-line "OUT=" f)
      (write-line "PWD=" f)
      (write-line "[MRU Local]" f)
      (write-line "MRU=2" f)
      (write-line "File0=" f)
      (write-line "File1=" f)
      (write-line "[MRU Sheet List]" f)
      (write-line "MRU=3" f)
      (write-line "File0=" f)
      (write-line "File1=" f)
      (write-line "File2=" f)
      (write-line "[PdfOptions]" f)
      (write-line "IncludeHyperlinks=TRUE" f)
      (write-line "CreateBookmarks=TRUE" f)
      (write-line "CaptureFontsInDrawing=TRUE" f)
      (write-line "ConvertTextToGeometry=FALSE" f)
      (write-line "VectorResolution=1200" f)
      (write-line "RasterResolution=400" f)
      (write-line "[AutoCAD Block Data]" f)
      (write-line "IncludeBlockInfo=0" f)
      (write-line "BlockTmplFilePath=" f)
      (write-line "[SheetSet Properties]" f)
      (write-line "IsSheetSet=FALSE" f)
      (write-line "IsHomogeneous=FALSE" f)
      (write-line "SheetSet Name=" f)
      (write-line "NoOfCopies=1" f)
      (write-line "PlotStampOn=FALSE" f)
      (write-line "ViewFile=FALSE" f)
      (write-line "JobID=0" f)
      (write-line "SelectionSetName=" f)
      (write-line "AcadProfile=<<Unnamed Profile>>" f)
      (write-line "CategoryName=" f)
      (write-line "LogFilePath=" f)
      (write-line "IncludeLayer=TRUE" f)
      (write-line "LineMerge=FALSE" f)
      (write-line "CurrentPrecision=" f)
      (write-line "PromptForDwfName=TRUE" f)
      (write-line "PwdProtectPublishedDWF=FALSE" f)
      (write-line "PromptForPwd=FALSE" f)
      (write-line "RepublishingMarkups=FALSE" f)
      (write-line "PublishSheetSetMetadata=FALSE" f)
      (write-line "PublishSheetMetadata=FALSE" f)
      (write-line "3DDWFOptions=0 1" f)
      (close f)
      dsdPath
    )
    nil
  )
)

(defun MDN-CreateAllDsds (root prefix / folders folder dwgs sorted dsdBase result made failed)
  (setq made 0 failed 0)
  (princ "\n\n========================================")
  (princ "\nCREATING SHEET LISTS")
  (princ "\n========================================")
  (setq folders (MDN-GetAllFolders root))
  (foreach folder folders
    (setq dwgs (MDN-GetFolderDwgs folder))
    (if dwgs
      (progn
        (setq sorted (MDN-SortDwgs dwgs))
        (setq dsdBase (MDN-GetDsdBaseName folder sorted prefix))
        (setq result (MDN-WriteDsd folder sorted dsdBase))
        (if result
          (progn
            (setq made (1+ made))
            (princ (strcat "\nCreated: " result " [" (itoa (length sorted)) " sheets]"))
          )
          (progn
            (setq failed (1+ failed))
            (princ (strcat "\nERROR creating DSD in: " folder))
          )
        )
      )
    )
  )
  (princ (strcat "\nSheet lists created: " (itoa made)))
  (princ (strcat "\nSheet list errors:   " (itoa failed)))
  (list made failed)
)

(defun c:MATCHDRAWING (/ choice targetTag projectPrefix folder answer dwgs total counter acad docs file doc openResult attrValue cleanValue oldBase oldName directory newName newPath renameResult correctCount renamedCount missingCount conflictCount errorCount dsdStats)
  (vl-load-com)
  (princ "\n\n========================================")
  (princ "\nMATCH DRAWING NAMES")
  (princ "\n========================================")

  (initget "CADFILE DWGNUMB")
  (setq choice (getkword "\nMatch filenames to [CADFILE/DWGNUMB] <DWGNUMB>: "))
  (if (null choice) (setq choice "DWGNUMB"))
  (if (= choice "CADFILE")
    (setq targetTag "AB_CADFILE")
    (setq targetTag "AB_DWGNUMB")
  )

  (setq projectPrefix (getstring T "\nEnter project prefix for special folders (example TX309): "))
  (setq projectPrefix (strcase (vl-string-trim " " projectPrefix)))

  (setq folder (getstring T "\nEnter top-level folder: "))
  (while (and (> (strlen folder) 0) (= (substr folder (strlen folder) 1) "\\"))
    (setq folder (substr folder 1 (1- (strlen folder))))
  )

  (princ "\nSearching folder and all subfolders...")
  (setq dwgs (MDN-GetAllDwgs folder))
  (setq total (length dwgs))
  (princ (strcat "\nFound " (itoa total) " drawing(s)."))
  (princ (strcat "\nFilename source: " targetTag))
  (princ (strcat "\nProject prefix:  " projectPrefix))
  (princ "\nAfter renaming, one DSD will be rebuilt for each folder containing DWGs.")

  (initget "Yes No")
  (setq answer (getkword "\nContinue? [Yes/No] <No>: "))
  (if (null answer) (setq answer "No"))

  (if (= answer "No")
    (princ "\nCancelled. No files were changed.")
    (progn
      (setq acad (vlax-get-acad-object))
      (setq docs (vla-get-Documents acad))
      (setq counter 0 correctCount 0 renamedCount 0 missingCount 0 conflictCount 0 errorCount 0)

      (foreach file dwgs
        (setq counter (1+ counter))
        (setq oldBase (vl-filename-base file))
        (setq oldName (strcat oldBase ".dwg"))
        (setq directory (vl-filename-directory file))
        (princ (strcat "\n\n[" (itoa counter) "/" (itoa total) "] " oldName))

        (setq openResult (vl-catch-all-apply 'vla-open (list docs file)))
        (if (vl-catch-all-error-p openResult)
          (progn
            (setq errorCount (1+ errorCount))
            (princ (strcat "\nERROR opening: " (vl-catch-all-error-message openResult)))
          )
          (progn
            (setq doc openResult)
            (setq attrValue (MDN-GetAttributeValue doc targetTag))
            (vl-catch-all-apply 'vla-close (list doc :vlax-false))
            (setq doc nil)

            (if (null attrValue)
              (progn
                (setq missingCount (1+ missingCount))
                (princ (strcat "\nSKIPPED - " targetTag " missing or blank."))
              )
              (progn
                (setq cleanValue (MDN-CleanName attrValue))
                (setq newName (strcat cleanValue ".dwg"))
                (setq newPath (strcat directory "\\" newName))
                (princ (strcat "\n" targetTag " = " cleanValue))

                (if (= (strcase oldBase) (strcase cleanValue))
                  (progn
                    (setq correctCount (1+ correctCount))
                    (princ "\nOK - Filename already matches.")
                  )
                  (if (findfile newPath)
                    (progn
                      (setq conflictCount (1+ conflictCount))
                      (princ (strcat "\nSKIPPED - Target already exists: " newName))
                    )
                    (progn
                      (setq renameResult (vl-catch-all-apply 'vl-file-rename (list file newPath)))
                      (if (or (vl-catch-all-error-p renameResult) (null renameResult))
                        (progn
                          (setq errorCount (1+ errorCount))
                          (princ "\nERROR - File could not be renamed.")
                        )
                        (progn
                          (setq renamedCount (1+ renamedCount))
                          (princ (strcat "\nRENAMED: " oldName " -> " newName))
                        )
                      )
                    )
                  )
                )
              )
            )
          )
        )
      )

      ;; Build DSDs only after every rename is complete.
      (setq dsdStats (MDN-CreateAllDsds folder projectPrefix))

      (princ "\n\n========================================")
      (princ "\nMATCH DRAWING COMPLETE")
      (princ "\n========================================")
      (princ (strcat "\nDrawings checked:    " (itoa total)))
      (princ (strcat "\nAlready correct:     " (itoa correctCount)))
      (princ (strcat "\nRenamed:             " (itoa renamedCount)))
      (princ (strcat "\nMissing/blank attr:  " (itoa missingCount)))
      (princ (strcat "\nName conflicts:      " (itoa conflictCount)))
      (princ (strcat "\nRename/open errors:  " (itoa errorCount)))
      (princ (strcat "\nSheet lists created: " (itoa (car dsdStats))))
      (princ (strcat "\nSheet list errors:   " (itoa (cadr dsdStats))))
      (princ "\n========================================")
    )
  )
  (princ)
)

(princ "\nMatchDrawingNames loaded successfully.")
(princ "\nType MATCHDRAWING to run.")
(princ)
